//
// Original Copyright (c) 2026 AIRBUS and its affiliates.
// This Source Code Form is subject to the terms of the Mozilla Public
// License, v. 2.0. If a copy of the MPL was not distributed with this
// file, You can obtain one at http://mozilla.org/MPL/2.0/.
//

library package CoSMAViewsPackage {

	view RequirementsTableView {
		//expose Requirements::MissionRequirementsPackage::*;
		//filter hastype SysML::Systems::RequirementDefinition;
	}
}
