package TechnicalIndividualsPackage {

	private import CoSMAPackage::*;
	private import TechnicalComponentsPackage::*;
	private import CoSMAQuantitiesAndUnitsPackage::*;
	private import SI::*;
	private import ISQ::*;
	individual part def 'FARP-SBRB' :> FARPNetworkInfrastructureFourSites {
		doc /* Forward Arming and Refueling Point at SBRB (9°52'12.82"S, 67°53'44.23"O), 2,158 m asphalt runway */
	}
	individual part def 'FARP-SBCZ' :> FARPNetworkInfrastructureFourSites {
		doc /* Forward Arming and Refueling Point at SBCZ (7°35'59.86"S, 72°46'23.12"O), 2,400 m asphalt runway */
	}
	individual part def 'FARP-SDCG' :> FARPNetworkInfrastructureFourSites {
		doc /* Forward Arming and Refueling Point at SDCG (3°28'9.00"S, 68°55'16.00"O), 1,200 m concrete runway */
	}
	individual part def 'FARP-SWKU' :> FARPNetworkInfrastructureFourSites {
		doc /* Forward Arming and Refueling Point at SWKU (1°7'11.98"N, 66°50'29.59"O), 1,200 m asphalt runway */
	}
	individual part def 'A29-Baseline-1' :> A29SuperTucanoAirframeBaseline {
		doc /* A-29 Super Tucano baseline configuration instance (A-29-1) */
	}
	individual part def 'A29-Baseline-2' :> A29SuperTucanoAirframeBaseline {
		doc /* A-29 Super Tucano baseline configuration instance (A-29-2) */
	}
	individual part def 'A29-Baseline-3' :> A29SuperTucanoAirframeBaseline {
		doc /* A-29 Super Tucano baseline configuration instance (A-29-3) */
	}
	individual part def 'A29-Baseline-4' :> A29SuperTucanoAirframeBaseline {
		doc /* A-29 Super Tucano baseline configuration instance (A-29-4) */
	}
	individual part def 'A29-Baseline-5' :> A29SuperTucanoAirframeBaseline {
		doc /* A-29 Super Tucano baseline configuration instance (A-29-5) */
	}
	individual part def 'A29-Baseline-6' :> A29SuperTucanoAirframeBaseline {
		doc /* A-29 Super Tucano baseline configuration instance (A-29-6) */
	}
	individual part def 'A29N-Modernized-1' :> A29SuperTucanoAirframeModernizedA29N {
		doc /* A-29 Super Tucano modernized (A-29N) configuration instance with C-UAS avionics */
	}
	individual part def 'A29N-Modernized-2' :> A29SuperTucanoAirframeModernizedA29N {
		doc /* A-29 Super Tucano modernized (A-29N) configuration instance with C-UAS avionics */
	}
	individual part def 'A29N-Modernized-3' :> A29SuperTucanoAirframeModernizedA29N {
		doc /* A-29 Super Tucano modernized (A-29N) configuration instance with C-UAS avionics */
	}
	individual part def 'A29N-Modernized-4' :> A29SuperTucanoAirframeModernizedA29N {
		doc /* A-29 Super Tucano modernized (A-29N) configuration instance with C-UAS avionics */
	}
	individual part def 'A29N-Modernized-5' :> A29SuperTucanoAirframeModernizedA29N {
		doc /* A-29 Super Tucano modernized (A-29N) configuration instance with C-UAS avionics */
	}
	individual part def 'A29N-Modernized-6' :> A29SuperTucanoAirframeModernizedA29N {
		doc /* A-29 Super Tucano modernized (A-29N) configuration instance with C-UAS avionics */
	}
	individual part def 'E99M-01' :> EMB145AEWCAirframeE99M {
		doc /* EMB-145 AEW&C airframe (E-99M) for Continental ZIDA Shield operation */
	}
	individual part def 'CINDACTA-Northern' :> CINDACTAIVRegionalControlCenter {
		doc /* CINDACTA IV Regional Control Center serving Northern region of Brazil */
	}
}
