package ContinentalZIDAShieldOperationModel {

	// CoSMA framework
	private import CoSMAPackage::*;
	private import CoSMAQuantitiesAndUnitsPackage::*;
	private import CoSMAViewsPackage::*;

	// Purpose layer
	private import CapabilitiesPackage::*;
	private import ContextPackage::*;
	private import MissionPackage::*;
	private import MissionPhasesPackage::*;
	private import MissionSpecificationPackage::*;
	private import StakeholderPackage::*;

	// Operation layer
	private import OperationsPackage::*;

	// Function layer
	private import FunctionsPackage::*;
	private import FunctionSpecificationPackage::*;

	// Logical layer
	private import LogicalComponentsPackage::*;

	// Technical layer
	private import SystemPackage::*;
	private import SystemSpecificationPackage::*;
	private import TechnicalComponentsPackage::*;
	private import TechnicalPortsPackage::*;
	private import TechnicalIndividualsPackage::*;

	// Program
	private import ProgramPackage::*;

	// Requirements
	private import MissionRequirementsPackage::*;
	private import FunctionalRequirementsPackage::*;
	private import TechnicalRequirementsPackage::*;
	private import StakeholderNeedsPackage::*;

	// Analysis
	private import AnalysisPackage::*;
	private import CalculationsPackage::*;

	// Execution
	private import MissionExecutionPackage::*;
}
